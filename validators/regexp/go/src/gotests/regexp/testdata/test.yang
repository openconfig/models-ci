module regexp-test {
  prefix "rt";
  namespace "urn:openconfig-test";

  import openconfig-types { prefix "oct"; }
  import openconfig-bgp-types { prefix "ocbgpt"; }
  import openconfig-inet-types { prefix "ocinet"; }
  import openconfig-packet-match-types { prefix "oc-pkt-match-types"; }

  leaf ipv4-address { type ocinet:ipv4-address; }
  leaf ip-address { type ocinet:ip-address; }
  leaf bgp-std-community { type ocbgpt:bgp-std-community-type; }
  leaf bgp-ext-community { type ocbgpt:bgp-ext-community-type; }
  leaf ipv6-address { type ocinet:ipv6-address; }
  leaf ipv4-prefix { type ocinet:ipv4-prefix; }
  leaf ipv6-prefix { type ocinet:ipv6-prefix; }
  leaf ip-prefix { type ocinet:ip-prefix; }
  leaf domain-name { type ocinet:domain-name; }
  leaf port-num-range { type oc-pkt-match-types:port-num-range; }
}
