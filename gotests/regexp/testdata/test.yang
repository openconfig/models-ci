module regexp-test {
  prefix "rt";
  namespace "urn:openconfig-test";

  import openconfig-types { prefix "oct"; }
  import openconfig-bgp-types { prefix "ocbgpt"; }

  leaf ipv4-address { type oct:ipv4-address; }
  leaf ip-address { type oct:ip-address; }
  leaf bgp-std-community { type ocbgpt:bgp-std-community-type; }
  leaf bgp-ext-community { type ocbgpt:bgp-ext-community-type; }
  leaf ipv6-address { type oct:ipv6-address; }
  leaf ipv4-prefix { type oct:ipv4-prefix; }
  leaf ipv6-prefix { type oct:ipv6-prefix; }
  leaf ip-prefix { type oct:ip-prefix; }
}
